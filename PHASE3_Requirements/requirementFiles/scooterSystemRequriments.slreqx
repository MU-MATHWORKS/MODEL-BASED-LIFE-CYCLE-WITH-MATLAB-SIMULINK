# scooterSystemRequriments
Scooter requirements defined as in document Scooter requirements.docx

## #1: Turn on (Container)
Requirements linked to function Turn on

### #2: Scooter turn on/off (Functional)
Users shall be able to turn on/off the scooter.

### #4: Turn on/off switch (Functional)
The scooter shall have only one mechanical turn on/off switch.

### #5: Battery connection when turn on (Functional)
The scooter shall connect the battery to the electric drive when the turn on/off button is in ON position while SOC is more than 10 %.

### #6: Software initialization when turn on (Functional)
The scooter shall initialize all software tasks when the turn on/off button is in ON position while SOC is more than 10 %.

### #7: Display SOC on turn on (Functional)
The scooter shall display initial SOC when the turn on/off button is in ON position while SOC is more than 10 %.

### #8: Turn on when SOC less than 10 % (Functional)
The scooter shall display a no battery sign in the display when the SOC is less than 10 %.
- Keywords: battery, SOC, turn on

## #9: Turn off (Container)
Requirements linked to turn off function.

### #11: Battery disconnection when turn off (Functional)
The scooter shall disconnect the battery from the electric drive when the turn on/off button is in OFF position.

### #12: Controller data when turn off (Functional)
The scooter shall remove all the data in the volatile memory of the controller.

## #10: Accelerate (Container)
Requirements linked to accelerate function

### #14: Mechanical throttle (Informational)
The scooter shall have a mechanical throttle.

### #15: Torque control (Functional)
The scooter shall control motor torque depending on the level of the mechanical throttle.

### #17: Acceleration rate (Functional)
The scooter shall accelerate from 0 to maximum speed in 6 seconds at the following conditions: maximum rider weight, 100 % SOC, tires inflated to the manufacture specifications, flat ground, maximum performance configuration.
- Keywords: Acceleration, speed

## #13: Brake (Container)
Requirements linked to brake function

### #18: Mechanical brake (Functional)
The scooter shall have a mechanical brake installed in the rear wheel.

### #19: Deceleration rate (Functional)
The scooter decelerate from maximum speed to zero in 6 seconds at the following conditions: maximum rider weight, 100 % SOC, tires inflated to the manufacture specifications, flat ground, maximum performance configuration.

### #20: Braking distance (Functional)
The scooter shall be able to stop form 25 km/h within a maximum distance of 2 m when the mechanical brake is applied.

### #29: Speed display steps (Functional)
The scooter shall display its actual speed in 2 km/h steps.

## #21: Ride (Container)
Requirements linked to ride function

### #22: Top speed (Functional)
The scooter shall be able to ride at maximum top speed of 25 km/h ± 2 km/h

### #23: Hill climbing capability (Functional)
The scooter shall be able to climb an 80 m long 10 % average grade hill in a maximum of 10 s with an average speed of 10 km/h.

### #24: Standard testing profile (Functional)
The scooter shall be able to accelerate until maximum speed, ride 10 seconds in maximum speed, and decelerate until stop at the following conditions: maximum rider weight, fully charged, tires inflated to the manufacture specifications, flat ground, maximum performance configuration.

### #25: Battery range (Functional)
The scooter shall have a range of at least 80 km under the following conditions: 5 % average slope hill, maximum rider weight, fully charged, tires inflated to the manufacture specifications, maximum performance configuration (no energy saving mode), maximum acceleration requested in all the accelarions. The scooter is ridden until battery dies completely.
- Keywords: battery, range

## #26: Display speed (Container)
Requirements linked to display speed function

### #28: Speed display unit (Functional)
The scooter shall display its actual speed in km/h.

### #30: Speed measurement precission (Functional)
The scooter shall measure its actual speed with a maximum error of 2% with respect to the real speed.

### #64: Speed display steps (Functional)
The scooter shall display its actual speed in 2 km/h steps

## #27: Display SOC (Container)
Requirements linked to SOC display

### #31: SOC display (Functional)
The scooter shall display its actual SOC in percentage respect to its full battery state.

### #32: SOC display steps (Functional)
The scooter shall display its actual SOC in 5 % steps.

### #33: SOC estimation precission (Functional)
The scooter shall estimate its actual SOC with a maximum error of 5 % with respect to the real SOC.

## #34: Charge battery (Container)
Requirements linked to battery charging function

### #35: Battery charging power source (Functional)
The scooter shall charge the battery from the utility grid.

### #36: Charging time (Functional)
The scooter shall charge the battery from 30 % to 80 % of SOC in 2 hours.

## #37: Limit propulsion torque (Container)
Requirements related to propulsion torque limit

### #38: Limit torque (Functional)
The scooter shall receive a limit torque flag from the user smartphone.

### #39: Propulsion torque limitation level (Functional)
The scooter shall limit its propulsion torque to 50 % of its maximum torque when the limit torque flag is activated.

## #40: Fold scooter (Container)
Requirements linked to scooter folding

### #41: Fold scooter (Functional)
The scooter shall be folded.

### #42: Folding size (Functional)
Folded size shall be length 45.5 x height 46.1 x width 19.8 inches

## #43: Unfold scooter (Container)
Requirements linked to scooter unfolding

### #44: Scooter unfold (Functional)
The scooter shall be unfolded

### #45: Unfolded size (Functional)
Unfolded size shall be length 45.5 x height 46.1 x width 21.3 inches

## #46: Install/Remove battery (Container)
Requirements linked to battery installation and removal

### #61: Battery removal (Informational)
The battery shall be removed.

### #62: Battery replacement (Informational)
The battery shall be replaced.

### #63: Battery removing safety (Informational)
The battery shall include safety measures to avoid short-circuiting it while installing/removing.

## #47: Install/Remove wheels (Container)
Requirements linked to wheel installation and removal

### #56: Wheel removal (Informational)
Front and rear wheels shall be removed

### #59: Wheel replacing (Informational)
Front and rear wheel shall be replaced

## #48: Miscellaneous (Container)
Other requirements

### #50: Weight (Informational)
Maximum scooter weight shall be 20 kg ± 2 kg

### #51: Wheel diameter (Informational)
Maximum wheel diameter shall be 125 mm

### #52: Motor mounting (Informational)
Motor shall be embedded in the front wheel

### #53: Rider weight (Informational)
The rider shall weight a maximum of 100 kg

### #54: Operating temperature (Functional)
The scooter shall be able to give rated power at an ambient temperature between -10 °C and 40 °C at the following conditions: maximum rider weight, fully charged, tires inflated to the manufacture specifications, flat ground, maximum performance configuration.
