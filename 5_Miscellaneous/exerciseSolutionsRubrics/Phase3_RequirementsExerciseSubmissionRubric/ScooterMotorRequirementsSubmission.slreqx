# ScooterMotorRequirements

## #4: Size (Informational)
The motor shall fit on a 10 inch diameter inflatable wheel.

## #6: Standard test contidions (Informational)
The standard test conditions for the electric scooter shall be in a smooth road with a maximum gradient of 5% and a load of 90 kg (not including the scooter's weight).

## #7: Motor Ratings (Functional)

### #1: Maximum Torque (Functional)
The motor shall have a maximum torque output of 10 Nm under standard test conditions.
- Rationale: The maximum torque required in the whole route is 7.2 Nm, so a maximum torque of 10 Nm has been established.

### #2: Maximum Speed (Functional)
The motor shall have a top speed of 530 rpm under standard test conditions.

### #3: Maximum Power (Functional)
The motor shall have a maximum power output of 500 W under standard test conditions.

### #5: Nominal Torque (Functional)
The motor shall have a nominal torque output of 1 Nm under standard test conditions.

### #24: Nominal Voltage (Functional)
The motor shall have a nominal voltage of 24 V.

## #9: Security and comfort (Functional)

### #10: Cogging torque (Functional)
The motor shall have a maximum cogging torque of 8 % under standard conditions.

### #11: Braking (Functional)
The motor shall have a braking system that can bring the scooter to a stop within 5 meters when traveling at a speed of 25 km/h.

### #12: Shut down (Functional)
The motor shall have a temperature sensor and shall shut down automatically if the temperature exceeds 80 ºC.

### #13: Shock immunity (Informational)
The motor shall have a robust design that can withstand a drop test from a height of 1 meter without damage.

### #14: Noise level (Informational)
The motor noise level shall be less than 70 dB at a distance of 1 meter while travelling at it's maximum speed.

### #22: Balancing (Informational)
The motor and the 10 inch inflatable tires shall be dynamically balanced.

## #15: Performance (Functional)

### #17: Throttle response (Functional)
The motor shall have a response time of less than 100 ms when the throttle is applied under standard conditions.

### #18: Power delivery (Functional)
The motor shall have a maximum power ripple of 5 % in it's whole speed range under standard test conditons to achieve a smooth and consistent power delivery.

### #19: Efficiency (Functional)
The motor efficiency shall be at least 80 % under standard test conditions.

### #20: Temperature range (Informational)
The motor shall be able to operate in temperatures ranging from -10 ºC to 50 ºC.

## #21: Direction (Functional)
The motor shall be able to operate in both forward and reverse directions.
